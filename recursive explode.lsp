(vl-load-com)
(defun c:rex (/ explodable adoc exp_lst not_explodable ss)

  (defun explodable (ss / i lst name obj)
    (repeat (setq i (sslength ss))
      (setq obj  (vlax-ename->vla-object (ssname ss (setq i (1- i))))
            name (vla-get-effectivename obj)
      )
      (if (and (not (vl-position name not_explodable))
               (vlax-write-enabled-p obj)
          )
        (setq lst (cons obj lst))
      )
    )
    lst
  )

  (setq adoc (vla-get-activedocument (vlax-get-acad-object)))
  (vla-startundomark adoc)
  (vlax-for blk (vla-get-Blocks adoc)
    (if (or (eq (vla-get-explodable blk) :vlax-false)
            (eq (vla-get-isxref blk) :vlax-true)
        )
      (setq not_explodable (cons (vla-get-name blk) not_explodable))
    )
  )
  (while (and (setq ss (ssget "_X" '((0 . "INSERT"))))
              (setq exp_lst (explodable ss))
         )
    (foreach blk exp_lst
      (vla-explode blk)
      (vla-delete blk)
    )
  )
  (vla-endundomark adoc)
  (princ)
)
